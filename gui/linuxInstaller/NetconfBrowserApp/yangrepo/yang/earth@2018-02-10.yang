module earth {

    yang-version 1;

    namespace "urn:ietf:params:xml:ns:yang:earth";

    prefix ear;

    organization "earth Description";

    contact "email: user@org.com";

    description "This module is a basic yang file";

    revision "2018-02-10" {
      description "Initial revision.";
      reference "RFC XXX";
    }
    
    container earthinfo {

	    leaf info1 {
	      type int32;
	      config false;
	      description "Added by me";
	    }	
	    
	    list country {
      		key "name";
      		description "Country info";

		    leaf name {
		      type string;
		      description "Column one of listM";
		    }

		   leaf gdp {
		      type string;
		      description "Column one of listM";
		    }
		    
		    leaf size {
		      type string;
		      description "Column one of listM";
		    }
		    
		      leaf-list regions {
		 	type string;
		 	description "Device Model";
	    }
		
		    container cities {
			leaf counter {
	      			type int32;
	      			config false;
	      			description "Added by me";
	    		}
			list city {
		      		key "name";
      				description "Country info";

			    leaf name {
			      type string;
			      description "Column one of listM";
			    }
			    leaf population {
			      type string;
			      description "Column one of listM";
			    }
			    leaf size {
		      		type string;
		      		description "Column one of listM";
		    	}
			}
		     
		    }
	     }
	}
	
}
